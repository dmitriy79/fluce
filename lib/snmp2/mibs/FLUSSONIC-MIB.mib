FLUSSONIC-MIB DEFINITIONS ::= BEGIN

IMPORTS
    MODULE-IDENTITY, OBJECT-TYPE, NOTIFICATION-TYPE,
    Integer32, snmpModules, experimental, enterprises,
    Gauge32, Counter64
        FROM SNMPv2-SMI
    MODULE-COMPLIANCE, OBJECT-GROUP, NOTIFICATION-GROUP
        FROM SNMPv2-CONF
    DisplayString, RowStatus
	FROM SNMPv2-TC;


flussonicModule MODULE-IDENTITY
	LAST-UPDATED "201604151800Z"
	ORGANIZATION "ERLYVIDEO LLC"
	CONTACT-INFO " e-mail:info@erlyvideo.org"

	DESCRIPTION
		"Flussonic SMI"
	REVISION   "201705241855Z"
	DESCRIPTION "Flussonic streams mib"
	::= { enterprises 36342 }

flussonic OBJECT IDENTIFIER ::= { flussonicModule 1 }
flussonicConformance OBJECT IDENTIFIER ::= { flussonicModule 2 }

streams OBJECT IDENTIFIER ::= { flussonic 1 }

streamsNum OBJECT-TYPE
  SYNTAX Gauge32
  MAX-ACCESS read-only
  STATUS current
  DESCRIPTION "Count stream"
  ::= { streams 1 }


          streamsTable OBJECT-TYPE
              SYNTAX  SEQUENCE OF StreamsEntry
              MAX-ACCESS  not-accessible
              STATUS   current
              DESCRIPTION
                      "A list of streams."
              ::= { streams 2 }

          streamsEntry OBJECT-TYPE
              SYNTAX  StreamsEntry
              MAX-ACCESS  not-accessible
              STATUS  current
              DESCRIPTION
                      ""
              INDEX   { sIndex }
              ::= { streamsTable 1 }

          StreamsEntry ::= SEQUENCE {
		            sIndex       INTEGER,
                sName        DisplayString,
                sClientCount Gauge32,
                sRetryCount  Gauge32,
                sLifeTime    Counter64,
		            sBitrate     Counter64,
		            sBytesIn     Counter64,
		            sBytesOut    Counter64,
                sStatus      RowStatus
          }

          sIndex OBJECT-TYPE
              SYNTAX      INTEGER
              MAX-ACCESS  read-only
              STATUS      current
               DESCRIPTION
                      "number of stream"
              ::= { streamsEntry 1 }

          sName OBJECT-TYPE
              SYNTAX      DisplayString (SIZE (0..255))
              MAX-ACCESS  read-only
              STATUS      current
              DESCRIPTION
                      "Name of a stream"
              ::= { streamsEntry 2 }

          sClientCount OBJECT-TYPE
              SYNTAX      Gauge32
              MAX-ACCESS  read-only
              STATUS      current
              DESCRIPTION
                      "Count clients on stream"
              ::= { streamsEntry 3 }

          sRetryCount OBJECT-TYPE
              SYNTAX      Gauge32
              MAX-ACCESS  read-only
              STATUS      current
              DESCRIPTION
                      "Count retries on stream"
              ::= { streamsEntry 4 }

          sLifeTime OBJECT-TYPE
              SYNTAX      Counter64
              MAX-ACCESS  read-only
              STATUS      current
              DESCRIPTION
                      "Stream lifetime"
              ::= { streamsEntry 5 }


          sBitrate OBJECT-TYPE
              SYNTAX      Counter64
              MAX-ACCESS  read-only
              STATUS      current
              DESCRIPTION
                      "Stream bitrate"
              ::= { streamsEntry 6 }

          sBytesIn OBJECT-TYPE
              SYNTAX      Counter64
              MAX-ACCESS  read-only
              STATUS      current
              DESCRIPTION
                      "Stream bytes in"
              ::= { streamsEntry 7 }

          sBytesOut OBJECT-TYPE
              SYNTAX      Counter64
              MAX-ACCESS  read-only
              STATUS      current
              DESCRIPTION
                      "Stream bytes out"
              ::= { streamsEntry 8 }

           sStatus OBJECT-TYPE
              SYNTAX      RowStatus
              MAX-ACCESS  read-only
              STATUS      current
              DESCRIPTION
                      "The status of this conceptual row."
              ::= { streamsEntry 9 }


accounting OBJECT IDENTIFIER ::= { flussonic 2 }

totalClients OBJECT-TYPE
  SYNTAX Gauge32
  MAX-ACCESS read-only
  STATUS current
  DESCRIPTION "Total number of clients"
  ::= { accounting 1 }


serverStatus OBJECT IDENTIFIER ::= { flussonic 3 }

schedulerLoad OBJECT-TYPE
    SYNTAX Gauge32
    MAX-ACCESS read-only
    STATUS current
    DESCRIPTION "Erlanf scheduler utilization, %"
        ::= { serverStatus 1}


streamGroup OBJECT-GROUP
	OBJECTS { streamsNum, sIndex, sName, sClientCount, sRetryCount, sLifeTime, sBitrate, sBytesIn, sBytesOut, sStatus }
	STATUS current
	DESCRIPTION "Streams group"
	::= { flussonicConformance 1 }

statGroup OBJECT-GROUP
	OBJECTS { totalClients }
	STATUS current
	DESCRIPTION "Statistics group"
	::= { flussonicConformance 2 }

statusGroup OBJECT-GROUP
	OBJECTS { schedulerLoad }
	STATUS current
	DESCRIPTION "Server status group"
	::= { flussonicConformance 3 }

END
